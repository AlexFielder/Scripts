(defun c:4v ()
(command "ucs" "w" "plan" "")
(command "zoom"  "e"  "zoom"  ".9x")
(command "-view" "save" "FRONT")
(command "ucs" "z" "90" "plan" "current")
(command "zoom"  "e"  "zoom"  ".9x")
(command "-view" "save" "RIGHT")
(command "ucs" "z" "90" "plan" "current")
(command "zoom"  "e"  "zoom"  ".9x")
(command "-view" "save" "BACK")
(command "ucs" "z" "90" "plan" "current")
(command "zoom"  "e"  "zoom"  ".9x")
(command "-view" "save" "LEFT")
(command "-view" "restore" "FRONT")
(princ))
